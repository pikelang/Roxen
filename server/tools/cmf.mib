--
-- ChiliMoon Foundation MIB
-- Copyright (C) 2002
--
-- This mib file defines the common OBJECT IDENTIFIER
-- used by all the CMF products
--
-- Creator: Honza Petrous (hop@pike.ida.liu.se)
--
-- $Id: cmf.mib,v 1.2 2002/11/27 07:22:23 _cvs_hop Exp $


CMF-MIB DEFINITIONS ::= 
BEGIN
	IMPORTS
		MODULE-IDENTITY, OBJECT-IDENTITY, OBJECT-TYPE,
		Integer32, Counter32, Unsigned32, enterprises
		    FROM SNMPv2-SMI
		TEXTUAL-CONVENTION, DisplayString
		    FROM SNMPv2-TC
		MODULE-COMPLIANCE, OBJECT-GROUP
		    FROM SNMPv2-CONF
		TRAP-TYPE
		    FROM RFC-1215;

	cmf MODULE-IDENTITY
	    LAST-UPDATED "200211260000Z"
	    ORGANIZATION "ChiliMoon Foundation"
	    CONTACT-INFO
		 "E-mail: hop@pike.ida.liu.se"
	    DESCRIPTION
	         "The MIB module for CMF private objects."
	::= { enterprises 15377 }

--
-- All CMF specific objects must branch off of the above chilimoon root.    
-- The following objects are defined.
--
  
--
-- CMF Applications
--
	app OBJECT IDENTIFIER ::= { cmf 1 }

--
-- CMF LDAP OIDs
--
	ldapSchema OBJECT IDENTIFIER ::= { cmf 2 }

	attributes OBJECT IDENTIFIER ::= { ldapSchema 1 }

	objectClasses OBJECT IDENTIFIER ::= { ldapSchema 2 }

--
-- CMF Applications
--

--    
-- Internet Server		------------------------------
--    
	chilimoon OBJECT IDENTIFIER ::= { app 1 }

	global OBJECT IDENTIFIER ::= { chilimoon 1 }

	boot     OBJECT-TYPE
			SYNTAX  INTEGER { restart(1), shutdown(2) }
			MAX-ACCESS  read-write
			STATUS  current
			DESCRIPTION
			  "Object for rebooting server"
			::= { global 1 }

	vsCount   OBJECT-TYPE
			SYNTAX  Counter32
			MAX-ACCESS  read-only
			STATUS  current
			DESCRIPTION
                            "The total number of virtual servers."
			::= { global 2 }

	vsTable   OBJECT-TYPE
			SYNTAX  SEQUENCE OF VsEntry
			MAX-ACCESS  not-accessible
			STATUS  current
			DESCRIPTION
                            "The virtual server table."
			::= { chilimoon 2 }

	vsEntry   OBJECT-TYPE
			SYNTAX  VsEntry
			MAX-ACCESS  not-accessible
			STATUS  current
			DESCRIPTION
			    "An entry in the virtual server table."
			INDEX   { vsIndex }
			::= { vsTable 1 }
    
	VsEntry ::=
		SEQUENCE {
			vsIndex
			    INTEGER,
			vsName
			    DisplayString,
			vsDescription
			    DisplayString,
			vsSent
			    Counter32,
			vsReceived
			    Counter32,
			vsHeaders
			    Counter32,
			vsRequests
			    Counter32
		}


	vsIndex   OBJECT-TYPE
			SYNTAX  Integer32 (1..2147483647)
			MAX-ACCESS  read-only
			STATUS  current
			DESCRIPTION
			    "An index which uniquely identifies a
			     virtual server."
			::= { vsEntry 1 }
    
	vsName   OBJECT-TYPE
			SYNTAX  DisplayString (SIZE (0..255))
			MAX-ACCESS  read-only
			STATUS  current
			DESCRIPTION
			    "The description of a virtual server"
			::= { vsEntry 2 }
    
	vsDescription   OBJECT-TYPE
			SYNTAX  DisplayString (SIZE (0..255))
			MAX-ACCESS  read-only
			STATUS  current
			DESCRIPTION
			    "The description of a virtual server"
			::= { vsEntry 3 }
    
	vsSent     OBJECT-TYPE
			SYNTAX  Counter32
			MAX-ACCESS  read-write
			STATUS  current
			DESCRIPTION
			    " ... "
			::= { vsEntry 4 }
    
	vsReceived     OBJECT-TYPE
			SYNTAX  Counter32
			MAX-ACCESS  read-write
			STATUS  current
			DESCRIPTION
			    " ... "
			::= { vsEntry 5 }
    
	vsHeaders     OBJECT-TYPE
			SYNTAX  Counter32
			MAX-ACCESS  read-write
			STATUS  current
			DESCRIPTION
			    " ... "
			::= { vsEntry 6 }
    
	vsRequests     OBJECT-TYPE
			SYNTAX  Counter32
			MAX-ACCESS  read-write
			STATUS  current
			DESCRIPTION
			    " ... "
			::= { vsEntry 7 }

--
-- TRAP objects
--

--	vsStartTrap TRAP-TYPE
--			ENTERPRISE chilimoon
--			VARIABLES { vsIndex }
--			DESCRIPTION
--			    "This trap is sent whenever a virtual server
--			     is started."
--			::= 1

	trapGlobal OBJECT IDENTIFIER ::= { chilimoon 3 }

	serverDownTrap  OBJECT-TYPE
			SYNTAX  Integer32 (1..2147483647)
			MAX-ACCESS  read-only
			STATUS  current
			DESCRIPTION
			    "An index which uniquely identifies a
			     virtual server."
			::= { trapGlobal 1 }

	trapVs OBJECT IDENTIFIER ::= { chilimoon 4 }

	vsExternalTrap OBJECT IDENTIFIER ::= { trapVs 1 }

	vsStartTrap   OBJECT-TYPE
			SYNTAX  Integer32 (1..2147483647)
			MAX-ACCESS  read-only
			STATUS  current
			DESCRIPTION
			    "An index which uniquely identifies a
			     virtual server."
			::= { trapVs 2 }

	vsStopTrap   OBJECT-TYPE
			SYNTAX  Integer32 (1..2147483647)
			MAX-ACCESS  read-only
			STATUS  current
			DESCRIPTION
			    "An index which uniquely identifies a
			     virtual server."
			::= { trapVs 3 }

	vsConfChangedTrap   OBJECT-TYPE
			SYNTAX  Integer32 (1..2147483647)
			MAX-ACCESS  read-only
			STATUS  current
			DESCRIPTION
			    "An index which uniquely identifies a
			     virtual server."
			::= { trapVs 4 }

--    
-- Pike Interpreter		------------------------------
--    
---	pike OBJECT IDENTIFIER ::= { app 2 }
---

           
END
